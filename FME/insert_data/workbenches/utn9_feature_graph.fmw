FME workspace utn9_feature_graph.fmw

Parameters:
- DestDataset_POSTGIS_10 = sewer   # Connection
- DestDataset_POSTGRES_10 = sewer   # Connection
- DestDataset_POSTGIS_12 = sewer   # Connection
- DestDataset_POSTGRES_12 = sewer   # Connection
- DestDataset_POSTGRES_14 = sewer   # Connection
- DestDataset_POSTGIS_16 = sewer   # Connection
- DestDataset_POSTGIS_15 = sewer   # Connection
- DestDataset_POSTGRES = sewer   # Connection
- SourceDataset_CITYGML_3 = C:\Users\Xander\Dropbox\MSc Geomatics\Thesis\CityGML-Utility-Network-ADE\FME\create_citygml\sewer.gml   # Source CityGML File(s)

Readers:
- CITYGML_1: CITYGML from $(SourceDataset_CITYGML_3)

Writers:
- POSTGIS_1: POSTGIS to $(DestDataset_POSTGIS_10)
- POSTGRES_1: POSTGRES to $(DestDataset_POSTGRES_10)
- POSTGIS_2: POSTGIS to $(DestDataset_POSTGIS_12)
- POSTGRES_2: POSTGRES to $(DestDataset_POSTGRES_12)
- POSTGRES_3: POSTGRES to $(DestDataset_POSTGRES_14)
- POSTGIS_3: POSTGIS to $(DestDataset_POSTGIS_16)
- POSTGIS_4: POSTGIS to $(DestDataset_POSTGIS_15)
- POSTGRES_4: POSTGRES to $(DestDataset_POSTGRES)

LiquidMedium (reader CITYGML_1)
    attributes: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
ExteriorMaterial (reader CITYGML_1)
    attributes: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
CityModel (reader CITYGML_1)
    attributes: citygml_target_uri xml_buffer, gml_description xml_buffer, gml_name xml_buffer, gml_feature_member{}.xlink_href xml_buffer, citygml_appearance_member{}.xlink_href xml_buffer, citygml_city_object_member{}.xlink_href xml_buffer
Note: Step#7
citydb.utn9_node (writer POSTGIS_2)
    attributes: id serial,PrimaryKey, objectclass_id int4, gmlid varchar(80), gmlid_codespace varchar(80), name varchar(80), name_codespace varchar(80), description text, type varchar(80), connection_signature varchar(80), link_control varchar(80), feat_graph_id int4
Note: Step#6
citydb.utn9_feature_graph (writer POSTGRES_1)
    attributes: id serial,PrimaryKey, objectclass_id int4, gmlid varchar(80), gmlid_codespace varchar(80), name varchar(80), name_codespace varchar(80), description text, ntw_feature_id int4, ntw_graph_id int4
Note: Step#8
citydb.utn9_link (writer POSTGIS_4)
    attributes: id serial,PrimaryKey, objectclass_id int4, gmlid varchar(80), gmlid_codespace varchar(80), name varchar(80), name_codespace varchar(80), description text, direction char(1), link_control varchar(80), interfeature_link_type varchar(80), start_node_id int4, end_node_id int4, feat_graph_id int4, ntw_graph_id int4
Note: Step#4
citydb.utn9_network_graph (writer POSTGRES_2)
    attributes: id serial,PrimaryKey, objectclass_id int4, gmlid varchar(80), gmlid_codespace varchar(80), name varchar(80), name_codespace varchar(80), description text, network_id int4
Note: Step#3
citydb.utn9_network (writer POSTGRES_3)
    attributes: id int4,PrimaryKey, objectclass_id int4, network_parent_id int4, network_root_id int4, class varchar(80), function varchar(80), usage varchar(80), commodity_id int4
Note: Step#2
citydb.city_furniture (writer POSTGIS_3)
    attributes: id int4, class varchar(256), class_codespace varchar(4000), function varchar(1000), function_codespace varchar(4000), usage varchar(1000), usage_codespace varchar(4000), lod1_brep_id int4, lod2_brep_id int4, lod3_brep_id int4, lod4_brep_id int4, lod1_implicit_rep_id int4, lod2_implicit_rep_id int4, lod3_implicit_rep_id int4, lod4_implicit_rep_id int4, lod1_implicit_transformation varchar(1000), lod2_implicit_transformation varchar(1000), lod3_implicit_transformation varchar(1000), lod4_implicit_transformation varchar(1000)
Note: Step#5
citydb.utn9_network_feature (writer POSTGIS_1)
    attributes: id int4,PrimaryKey, objectclass_id int4, ntw_feature_parent_id int4, ntw_feature_root_id int4, class varchar(80), connected_cto varchar(80), function varchar(80), usage varchar(80), year_of_construction date, status varchar(80), location_quality varchar(80), elevation_quality varchar(80), cityobject_id int4, prot_element_id int4
GeometryRemover
    -> AttributeKeeper_9
AttributeKeeper_9
    KEEP_ATTRS = gml_id,id,objectclass_id
    -> AttributeRenamer_13
AttributeRenamer_13
    ATTR_TABLE:
      RENAME_SET_DEFAULT gml_id > gmlid
      RENAME_SET_DEFAULT objectclass_id
    -> citydb.cityobject (writer POSTGRES_4) [off]
Note: Step#1
citydb.cityobject (writer POSTGRES_4)
    attributes: id int4, objectclass_id int4, gmlid varchar(256), gmlid_codespace varchar(1000), name varchar(1000), name_codespace varchar(4000), description varchar(4000), creation_date timestamp, termination_date timestamp, relative_to_terrain varchar(256), relative_to_water varchar(256), last_modification_date timestamp, updating_person varchar(256), reason_for_update varchar(4000), lineage varchar(256), xml_source text

Bookmark: NetworkFeature - SimpleFunctionalElement
SimpleFunctionalElement (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), utility_medium_supply{}.utility_abstract_medium_supply_utility_potential_supply_utility_supply_utility_flow_rate xml_real64, utility_medium_supply{}.utility_abstract_medium_supply_utility_potential_supply_utility_supply_utility_flow_rate_units xml_buffer, utility_medium_supply{}.utility_abstract_medium_supply_utility_potential_supply_utility_supply_utility_status xml_char(16), utility_medium_supply{}.utility_abstract_medium_supply_utility_current_supply_utility_supply_utility_flow_rate xml_real64, utility_medium_supply{}.utility_abstract_medium_supply_utility_current_supply_utility_supply_utility_flow_rate_units xml_buffer, utility_medium_supply{}.utility_abstract_medium_supply_utility_current_supply_utility_supply_utility_status xml_char(16), utility_medium_supply{}.utility_abstract_medium_supply_utility_storage{}.utility_storage_utility_type xml_buffer, utility_medium_supply{}.utility_abstract_medium_supply_utility_storage{}.utility_storage_utility_type_codeSpace xml_buffer, utility_medium_supply{}.utility_abstract_medium_supply_utility_storage{}.utility_storage_utility_max_capacity xml_real64, utility_medium_supply{}.utility_abstract_medium_supply_utility_storage{}.utility_storage_utility_max_capacity_units xml_buffer, utility_medium_supply{}.utility_abstract_medium_supply_utility_storage{}.utility_storage_utility_fill_level xml_real64, utility_medium_supply{}.utility_abstract_medium_supply_utility_storage{}.utility_storage_utility_inflow_rate xml_real64, utility_medium_supply{}.utility_abstract_medium_supply_utility_storage{}.utility_storage_utility_inflow_rate_units xml_buffer, utility_medium_supply{}.utility_abstract_medium_supply_utility_storage{}.utility_storage_utility_outflow_rate xml_real64, utility_medium_supply{}.utility_abstract_medium_supply_utility_storage{}.utility_storage_utility_outflow_rate_units xml_buffer, utility_medium_supply{}.utility_electrical_medium_supply_utility_potential_supply_utility_supply_utility_flow_rate xml_real64,
      utility_medium_supply{}.utility_electrical_medium_supply_utility_potential_supply_utility_supply_utility_flow_rate_units xml_buffer, utility_medium_supply{}.utility_electrical_medium_supply_utility_potential_supply_utility_supply_utility_status xml_char(16), utility_medium_supply{}.utility_electrical_medium_supply_utility_current_supply_utility_supply_utility_flow_rate xml_real64, utility_medium_supply{}.utility_electrical_medium_supply_utility_current_supply_utility_supply_utility_flow_rate_units xml_buffer, utility_medium_supply{}.utility_electrical_medium_supply_utility_current_supply_utility_supply_utility_status xml_char(16), utility_medium_supply{}.utility_electrical_medium_supply_utility_storage{}.utility_storage_utility_type xml_buffer, utility_medium_supply{}.utility_electrical_medium_supply_utility_storage{}.utility_storage_utility_type_codeSpace xml_buffer, utility_medium_supply{}.utility_electrical_medium_supply_utility_storage{}.utility_storage_utility_max_capacity xml_real64, utility_medium_supply{}.utility_electrical_medium_supply_utility_storage{}.utility_storage_utility_max_capacity_units xml_buffer, utility_medium_supply{}.utility_electrical_medium_supply_utility_storage{}.utility_storage_utility_fill_level xml_real64, utility_medium_supply{}.utility_electrical_medium_supply_utility_storage{}.utility_storage_utility_inflow_rate xml_real64, utility_medium_supply{}.utility_electrical_medium_supply_utility_storage{}.utility_storage_utility_inflow_rate_units xml_buffer, utility_medium_supply{}.utility_electrical_medium_supply_utility_storage{}.utility_storage_utility_outflow_rate xml_real64, utility_medium_supply{}.utility_electrical_medium_supply_utility_storage{}.utility_storage_utility_outflow_rate_units xml_buffer, utility_medium_supply{}.utility_electrical_medium_supply_utility_type xml_char(29), utility_medium_supply{}.utility_optical_medium_supply_utility_potential_supply_utility_supply_utility_flow_rate xml_real64, utility_medium_supply{}.utility_optical_medium_supply_utility_potential_supply_utility_supply_utility_flow_rate_units xml_buffer, utility_medium_supply{}.utility_optical_medium_supply_utility_potential_supply_utility_supply_utility_status xml_char(16), utility_medium_supply{}.utility_optical_medium_supply_utility_current_supply_utility_supply_utility_flow_rate xml_real64, utility_medium_supply{}.utility_optical_medium_supply_utility_current_supply_utility_supply_utility_flow_rate_units xml_buffer, utility_medium_supply{}.utility_optical_medium_supply_utility_current_supply_utility_supply_utility_status xml_char(16), utility_medium_supply{}.utility_optical_medium_supply_utility_storage{}.utility_storage_utility_type xml_buffer, utility_medium_supply{}.utility_optical_medium_supply_utility_storage{}.utility_storage_utility_type_codeSpace xml_buffer, utility_medium_supply{}.utility_optical_medium_supply_utility_storage{}.utility_storage_utility_max_capacity xml_real64, utility_medium_supply{}.utility_optical_medium_supply_utility_storage{}.utility_storage_utility_max_capacity_units xml_buffer, utility_medium_supply{}.utility_optical_medium_supply_utility_storage{}.utility_storage_utility_fill_level xml_real64, utility_medium_supply{}.utility_optical_medium_supply_utility_storage{}.utility_storage_utility_inflow_rate xml_real64, utility_medium_supply{}.utility_optical_medium_supply_utility_storage{}.utility_storage_utility_inflow_rate_units xml_buffer, utility_medium_supply{}.utility_optical_medium_supply_utility_storage{}.utility_storage_utility_outflow_rate xml_real64, utility_medium_supply{}.utility_optical_medium_supply_utility_storage{}.utility_storage_utility_outflow_rate_units xml_buffer,
      utility_medium_supply{}.utility_optical_medium_supply_utility_type xml_char(7), utility_medium_supply{}.utility_liquid_medium_supply_utility_potential_supply_utility_supply_utility_flow_rate xml_real64, utility_medium_supply{}.utility_liquid_medium_supply_utility_potential_supply_utility_supply_utility_flow_rate_units xml_buffer, utility_medium_supply{}.utility_liquid_medium_supply_utility_potential_supply_utility_supply_utility_status xml_char(16), utility_medium_supply{}.utility_liquid_medium_supply_utility_current_supply_utility_supply_utility_flow_rate xml_real64, utility_medium_supply{}.utility_liquid_medium_supply_utility_current_supply_utility_supply_utility_flow_rate_units xml_buffer, utility_medium_supply{}.utility_liquid_medium_supply_utility_current_supply_utility_supply_utility_status xml_char(16), utility_medium_supply{}.utility_liquid_medium_supply_utility_storage{}.utility_storage_utility_type xml_buffer, utility_medium_supply{}.utility_liquid_medium_supply_utility_storage{}.utility_storage_utility_type_codeSpace xml_buffer, utility_medium_supply{}.utility_liquid_medium_supply_utility_storage{}.utility_storage_utility_max_capacity xml_real64, utility_medium_supply{}.utility_liquid_medium_supply_utility_storage{}.utility_storage_utility_max_capacity_units xml_buffer, utility_medium_supply{}.utility_liquid_medium_supply_utility_storage{}.utility_storage_utility_fill_level xml_real64, utility_medium_supply{}.utility_liquid_medium_supply_utility_storage{}.utility_storage_utility_inflow_rate xml_real64, utility_medium_supply{}.utility_liquid_medium_supply_utility_storage{}.utility_storage_utility_inflow_rate_units xml_buffer, utility_medium_supply{}.utility_liquid_medium_supply_utility_storage{}.utility_storage_utility_outflow_rate xml_real64, utility_medium_supply{}.utility_liquid_medium_supply_utility_storage{}.utility_storage_utility_outflow_rate_units xml_buffer, utility_medium_supply{}.utility_liquid_medium_supply_utility_type xml_buffer, utility_medium_supply{}.utility_liquid_medium_supply_utility_type_codeSpace xml_buffer, utility_medium_supply{}.utility_gaseous_medium_supply_utility_potential_supply_utility_supply_utility_flow_rate xml_real64, utility_medium_supply{}.utility_gaseous_medium_supply_utility_potential_supply_utility_supply_utility_flow_rate_units xml_buffer, utility_medium_supply{}.utility_gaseous_medium_supply_utility_potential_supply_utility_supply_utility_status xml_char(16), utility_medium_supply{}.utility_gaseous_medium_supply_utility_current_supply_utility_supply_utility_flow_rate xml_real64, utility_medium_supply{}.utility_gaseous_medium_supply_utility_current_supply_utility_supply_utility_flow_rate_units xml_buffer, utility_medium_supply{}.utility_gaseous_medium_supply_utility_current_supply_utility_supply_utility_status xml_char(16), utility_medium_supply{}.utility_gaseous_medium_supply_utility_storage{}.utility_storage_utility_type xml_buffer, utility_medium_supply{}.utility_gaseous_medium_supply_utility_storage{}.utility_storage_utility_type_codeSpace xml_buffer, utility_medium_supply{}.utility_gaseous_medium_supply_utility_storage{}.utility_storage_utility_max_capacity xml_real64, utility_medium_supply{}.utility_gaseous_medium_supply_utility_storage{}.utility_storage_utility_max_capacity_units xml_buffer, utility_medium_supply{}.utility_gaseous_medium_supply_utility_storage{}.utility_storage_utility_fill_level xml_real64, utility_medium_supply{}.utility_gaseous_medium_supply_utility_storage{}.utility_storage_utility_inflow_rate xml_real64,
      utility_medium_supply{}.utility_gaseous_medium_supply_utility_storage{}.utility_storage_utility_inflow_rate_units xml_buffer, utility_medium_supply{}.utility_gaseous_medium_supply_utility_storage{}.utility_storage_utility_outflow_rate xml_real64, utility_medium_supply{}.utility_gaseous_medium_supply_utility_storage{}.utility_storage_utility_outflow_rate_units xml_buffer, utility_medium_supply{}.utility_gaseous_medium_supply_utility_type xml_buffer, utility_medium_supply{}.utility_gaseous_medium_supply_utility_type_codeSpace xml_buffer, utility_medium_supply{}.utility_solid_medium_supply_utility_potential_supply_utility_supply_utility_flow_rate xml_real64, utility_medium_supply{}.utility_solid_medium_supply_utility_potential_supply_utility_supply_utility_flow_rate_units xml_buffer, utility_medium_supply{}.utility_solid_medium_supply_utility_potential_supply_utility_supply_utility_status xml_char(16), utility_medium_supply{}.utility_solid_medium_supply_utility_current_supply_utility_supply_utility_flow_rate xml_real64, utility_medium_supply{}.utility_solid_medium_supply_utility_current_supply_utility_supply_utility_flow_rate_units xml_buffer, utility_medium_supply{}.utility_solid_medium_supply_utility_current_supply_utility_supply_utility_status xml_char(16), utility_medium_supply{}.utility_solid_medium_supply_utility_storage{}.utility_storage_utility_type xml_buffer, utility_medium_supply{}.utility_solid_medium_supply_utility_storage{}.utility_storage_utility_type_codeSpace xml_buffer, utility_medium_supply{}.utility_solid_medium_supply_utility_storage{}.utility_storage_utility_max_capacity xml_real64, utility_medium_supply{}.utility_solid_medium_supply_utility_storage{}.utility_storage_utility_max_capacity_units xml_buffer, utility_medium_supply{}.utility_solid_medium_supply_utility_storage{}.utility_storage_utility_fill_level xml_real64, utility_medium_supply{}.utility_solid_medium_supply_utility_storage{}.utility_storage_utility_inflow_rate xml_real64, utility_medium_supply{}.utility_solid_medium_supply_utility_storage{}.utility_storage_utility_inflow_rate_units xml_buffer, utility_medium_supply{}.utility_solid_medium_supply_utility_storage{}.utility_storage_utility_outflow_rate xml_real64, utility_medium_supply{}.utility_solid_medium_supply_utility_storage{}.utility_storage_utility_outflow_rate_units xml_buffer, utility_medium_supply{}.utility_solid_medium_supply_utility_type xml_buffer, utility_medium_supply{}.utility_solid_medium_supply_utility_type_codeSpace xml_buffer, utility_role_in_network{}.xlink_href xml_buffer, citygml_appearance{}.xlink_href xml_buffer, utility_function xml_buffer, utility_function_codeSpace xml_buffer, utility_usage{} xml_buffer, utility_usage{}.codeSpace xml_buffer, utility_connected_city_object xml_buffer, utility_year_of_construction xml_date,
      utility_status xml_char(16), utility_location_quality xml_char(12), utility_elevation_quality xml_char(12), utility_consists_of{}.xlink_href xml_buffer, utility_has_material{}.xlink_href xml_buffer, utility_topo_graph_xlink_href xml_buffer, utility_occupied_hollow_space_xlink_href xml_buffer, citygml_level_of_detail{} xml_buffer, utility_class xml_buffer, utility_class_codeSpace xml_buffer
    -> Counter_2
Note: create id
Counter_2
    SCOPE = Global
    DOMAIN = cityobject_counter
    CNT_ATTR = SimpleFunctionalElement_id
    START = 1
    -> StringReplacer_3
    -> StringReplacer
Note: connectedCityObject: #gmli_id (URI) to gml_id
StringReplacer
    FIND_TEXT = #
    NO_MATCH = _FME_NO_OP_
    SRC_ATTRS = utility_connected_city_object
    CASE = NO
    REGEXP = NO
    -> FeatureMerger_12 [REQUESTOR]
Note: topoGraph xlink: #gmli_id to gml_id
StringReplacer_3
    FIND_TEXT = #
    NO_MATCH = _FME_NO_OP_
    SRC_ATTRS = utility_topo_graph_xlink_href
    CASE = NO
    REGEXP = NO
    -> FeatureMerger [SUPPLIER]
FeatureMerger_12
    MERGE_TYPE = Attributes Only
    IGNORE_NULLS = No
    REJECT_NULL_MISSING_KEYS = No
    PROCESS_DUPS = No
    JOIN_KEYS = @Value(utility_connected_city_object) @Value(gml_id) AUTO
    ATTR_ACCUM_MODE = Merge Supplier
    ATTR_CONFLICT_RES = Use Requestor
    SUPPLIERS_FIRST = No
    MERGED -> AttributeKeeper_2
AttributeKeeper_2
    KEEP_ATTRS = CityFurniture_id,gml_id,utility_class,utility_connected_city_object,SimpleFunctionalElement_id
    -> AttributeCreator_2
Note: objectclass_id = 343
AttributeCreator_2
    ATTR_TABLE = SET_TO objectclass_id = 343
    -> AttributeRenamer_2
Note: map attributes
AttributeRenamer_2
    ATTR_TABLE:
      RENAME_SET_DEFAULT SimpleFunctionalElement_id > id
      RENAME_SET_DEFAULT objectclass_id
      RENAME_SET_DEFAULT utility_connected_city_object > connected_cto
      RENAME_SET_DEFAULT CityFurniture_id > cityobject_id
    -> citydb.utn9_network_feature (writer POSTGIS_1) [off]
    -> GeometryRemover

Bookmark: NetworkFeature - RoundPipe
RoundPipe (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), utility_medium_supply{}.utility_abstract_medium_supply_utility_potential_supply_utility_supply_utility_flow_rate xml_real64, utility_medium_supply{}.utility_abstract_medium_supply_utility_potential_supply_utility_supply_utility_flow_rate_units xml_buffer, utility_medium_supply{}.utility_abstract_medium_supply_utility_potential_supply_utility_supply_utility_status xml_char(16), utility_medium_supply{}.utility_abstract_medium_supply_utility_current_supply_utility_supply_utility_flow_rate xml_real64, utility_medium_supply{}.utility_abstract_medium_supply_utility_current_supply_utility_supply_utility_flow_rate_units xml_buffer, utility_medium_supply{}.utility_abstract_medium_supply_utility_current_supply_utility_supply_utility_status xml_char(16), utility_medium_supply{}.utility_abstract_medium_supply_utility_storage{}.utility_storage_utility_type xml_buffer, utility_medium_supply{}.utility_abstract_medium_supply_utility_storage{}.utility_storage_utility_type_codeSpace xml_buffer, utility_medium_supply{}.utility_abstract_medium_supply_utility_storage{}.utility_storage_utility_max_capacity xml_real64, utility_medium_supply{}.utility_abstract_medium_supply_utility_storage{}.utility_storage_utility_max_capacity_units xml_buffer, utility_medium_supply{}.utility_abstract_medium_supply_utility_storage{}.utility_storage_utility_fill_level xml_real64, utility_medium_supply{}.utility_abstract_medium_supply_utility_storage{}.utility_storage_utility_inflow_rate xml_real64, utility_medium_supply{}.utility_abstract_medium_supply_utility_storage{}.utility_storage_utility_inflow_rate_units xml_buffer, utility_medium_supply{}.utility_abstract_medium_supply_utility_storage{}.utility_storage_utility_outflow_rate xml_real64, utility_medium_supply{}.utility_abstract_medium_supply_utility_storage{}.utility_storage_utility_outflow_rate_units xml_buffer, utility_medium_supply{}.utility_electrical_medium_supply_utility_potential_supply_utility_supply_utility_flow_rate xml_real64,
      utility_medium_supply{}.utility_electrical_medium_supply_utility_potential_supply_utility_supply_utility_flow_rate_units xml_buffer, utility_medium_supply{}.utility_electrical_medium_supply_utility_potential_supply_utility_supply_utility_status xml_char(16), utility_medium_supply{}.utility_electrical_medium_supply_utility_current_supply_utility_supply_utility_flow_rate xml_real64, utility_medium_supply{}.utility_electrical_medium_supply_utility_current_supply_utility_supply_utility_flow_rate_units xml_buffer, utility_medium_supply{}.utility_electrical_medium_supply_utility_current_supply_utility_supply_utility_status xml_char(16), utility_medium_supply{}.utility_electrical_medium_supply_utility_storage{}.utility_storage_utility_type xml_buffer, utility_medium_supply{}.utility_electrical_medium_supply_utility_storage{}.utility_storage_utility_type_codeSpace xml_buffer, utility_medium_supply{}.utility_electrical_medium_supply_utility_storage{}.utility_storage_utility_max_capacity xml_real64, utility_medium_supply{}.utility_electrical_medium_supply_utility_storage{}.utility_storage_utility_max_capacity_units xml_buffer, utility_medium_supply{}.utility_electrical_medium_supply_utility_storage{}.utility_storage_utility_fill_level xml_real64, utility_medium_supply{}.utility_electrical_medium_supply_utility_storage{}.utility_storage_utility_inflow_rate xml_real64, utility_medium_supply{}.utility_electrical_medium_supply_utility_storage{}.utility_storage_utility_inflow_rate_units xml_buffer, utility_medium_supply{}.utility_electrical_medium_supply_utility_storage{}.utility_storage_utility_outflow_rate xml_real64, utility_medium_supply{}.utility_electrical_medium_supply_utility_storage{}.utility_storage_utility_outflow_rate_units xml_buffer, utility_medium_supply{}.utility_electrical_medium_supply_utility_type xml_char(29), utility_medium_supply{}.utility_optical_medium_supply_utility_potential_supply_utility_supply_utility_flow_rate xml_real64, utility_medium_supply{}.utility_optical_medium_supply_utility_potential_supply_utility_supply_utility_flow_rate_units xml_buffer, utility_medium_supply{}.utility_optical_medium_supply_utility_potential_supply_utility_supply_utility_status xml_char(16), utility_medium_supply{}.utility_optical_medium_supply_utility_current_supply_utility_supply_utility_flow_rate xml_real64, utility_medium_supply{}.utility_optical_medium_supply_utility_current_supply_utility_supply_utility_flow_rate_units xml_buffer, utility_medium_supply{}.utility_optical_medium_supply_utility_current_supply_utility_supply_utility_status xml_char(16), utility_medium_supply{}.utility_optical_medium_supply_utility_storage{}.utility_storage_utility_type xml_buffer, utility_medium_supply{}.utility_optical_medium_supply_utility_storage{}.utility_storage_utility_type_codeSpace xml_buffer, utility_medium_supply{}.utility_optical_medium_supply_utility_storage{}.utility_storage_utility_max_capacity xml_real64, utility_medium_supply{}.utility_optical_medium_supply_utility_storage{}.utility_storage_utility_max_capacity_units xml_buffer, utility_medium_supply{}.utility_optical_medium_supply_utility_storage{}.utility_storage_utility_fill_level xml_real64, utility_medium_supply{}.utility_optical_medium_supply_utility_storage{}.utility_storage_utility_inflow_rate xml_real64, utility_medium_supply{}.utility_optical_medium_supply_utility_storage{}.utility_storage_utility_inflow_rate_units xml_buffer, utility_medium_supply{}.utility_optical_medium_supply_utility_storage{}.utility_storage_utility_outflow_rate xml_real64, utility_medium_supply{}.utility_optical_medium_supply_utility_storage{}.utility_storage_utility_outflow_rate_units xml_buffer,
      utility_medium_supply{}.utility_optical_medium_supply_utility_type xml_char(7), utility_medium_supply{}.utility_liquid_medium_supply_utility_potential_supply_utility_supply_utility_flow_rate xml_real64, utility_medium_supply{}.utility_liquid_medium_supply_utility_potential_supply_utility_supply_utility_flow_rate_units xml_buffer, utility_medium_supply{}.utility_liquid_medium_supply_utility_potential_supply_utility_supply_utility_status xml_char(16), utility_medium_supply{}.utility_liquid_medium_supply_utility_current_supply_utility_supply_utility_flow_rate xml_real64, utility_medium_supply{}.utility_liquid_medium_supply_utility_current_supply_utility_supply_utility_flow_rate_units xml_buffer, utility_medium_supply{}.utility_liquid_medium_supply_utility_current_supply_utility_supply_utility_status xml_char(16), utility_medium_supply{}.utility_liquid_medium_supply_utility_storage{}.utility_storage_utility_type xml_buffer, utility_medium_supply{}.utility_liquid_medium_supply_utility_storage{}.utility_storage_utility_type_codeSpace xml_buffer, utility_medium_supply{}.utility_liquid_medium_supply_utility_storage{}.utility_storage_utility_max_capacity xml_real64, utility_medium_supply{}.utility_liquid_medium_supply_utility_storage{}.utility_storage_utility_max_capacity_units xml_buffer, utility_medium_supply{}.utility_liquid_medium_supply_utility_storage{}.utility_storage_utility_fill_level xml_real64, utility_medium_supply{}.utility_liquid_medium_supply_utility_storage{}.utility_storage_utility_inflow_rate xml_real64, utility_medium_supply{}.utility_liquid_medium_supply_utility_storage{}.utility_storage_utility_inflow_rate_units xml_buffer, utility_medium_supply{}.utility_liquid_medium_supply_utility_storage{}.utility_storage_utility_outflow_rate xml_real64, utility_medium_supply{}.utility_liquid_medium_supply_utility_storage{}.utility_storage_utility_outflow_rate_units xml_buffer, utility_medium_supply{}.utility_liquid_medium_supply_utility_type xml_buffer, utility_medium_supply{}.utility_liquid_medium_supply_utility_type_codeSpace xml_buffer, utility_medium_supply{}.utility_gaseous_medium_supply_utility_potential_supply_utility_supply_utility_flow_rate xml_real64, utility_medium_supply{}.utility_gaseous_medium_supply_utility_potential_supply_utility_supply_utility_flow_rate_units xml_buffer, utility_medium_supply{}.utility_gaseous_medium_supply_utility_potential_supply_utility_supply_utility_status xml_char(16), utility_medium_supply{}.utility_gaseous_medium_supply_utility_current_supply_utility_supply_utility_flow_rate xml_real64, utility_medium_supply{}.utility_gaseous_medium_supply_utility_current_supply_utility_supply_utility_flow_rate_units xml_buffer, utility_medium_supply{}.utility_gaseous_medium_supply_utility_current_supply_utility_supply_utility_status xml_char(16), utility_medium_supply{}.utility_gaseous_medium_supply_utility_storage{}.utility_storage_utility_type xml_buffer, utility_medium_supply{}.utility_gaseous_medium_supply_utility_storage{}.utility_storage_utility_type_codeSpace xml_buffer, utility_medium_supply{}.utility_gaseous_medium_supply_utility_storage{}.utility_storage_utility_max_capacity xml_real64, utility_medium_supply{}.utility_gaseous_medium_supply_utility_storage{}.utility_storage_utility_max_capacity_units xml_buffer, utility_medium_supply{}.utility_gaseous_medium_supply_utility_storage{}.utility_storage_utility_fill_level xml_real64, utility_medium_supply{}.utility_gaseous_medium_supply_utility_storage{}.utility_storage_utility_inflow_rate xml_real64,
      utility_medium_supply{}.utility_gaseous_medium_supply_utility_storage{}.utility_storage_utility_inflow_rate_units xml_buffer, utility_medium_supply{}.utility_gaseous_medium_supply_utility_storage{}.utility_storage_utility_outflow_rate xml_real64, utility_medium_supply{}.utility_gaseous_medium_supply_utility_storage{}.utility_storage_utility_outflow_rate_units xml_buffer, utility_medium_supply{}.utility_gaseous_medium_supply_utility_type xml_buffer, utility_medium_supply{}.utility_gaseous_medium_supply_utility_type_codeSpace xml_buffer, utility_medium_supply{}.utility_solid_medium_supply_utility_potential_supply_utility_supply_utility_flow_rate xml_real64, utility_medium_supply{}.utility_solid_medium_supply_utility_potential_supply_utility_supply_utility_flow_rate_units xml_buffer, utility_medium_supply{}.utility_solid_medium_supply_utility_potential_supply_utility_supply_utility_status xml_char(16), utility_medium_supply{}.utility_solid_medium_supply_utility_current_supply_utility_supply_utility_flow_rate xml_real64, utility_medium_supply{}.utility_solid_medium_supply_utility_current_supply_utility_supply_utility_flow_rate_units xml_buffer, utility_medium_supply{}.utility_solid_medium_supply_utility_current_supply_utility_supply_utility_status xml_char(16), utility_medium_supply{}.utility_solid_medium_supply_utility_storage{}.utility_storage_utility_type xml_buffer, utility_medium_supply{}.utility_solid_medium_supply_utility_storage{}.utility_storage_utility_type_codeSpace xml_buffer, utility_medium_supply{}.utility_solid_medium_supply_utility_storage{}.utility_storage_utility_max_capacity xml_real64, utility_medium_supply{}.utility_solid_medium_supply_utility_storage{}.utility_storage_utility_max_capacity_units xml_buffer, utility_medium_supply{}.utility_solid_medium_supply_utility_storage{}.utility_storage_utility_fill_level xml_real64, utility_medium_supply{}.utility_solid_medium_supply_utility_storage{}.utility_storage_utility_inflow_rate xml_real64, utility_medium_supply{}.utility_solid_medium_supply_utility_storage{}.utility_storage_utility_inflow_rate_units xml_buffer, utility_medium_supply{}.utility_solid_medium_supply_utility_storage{}.utility_storage_utility_outflow_rate xml_real64, utility_medium_supply{}.utility_solid_medium_supply_utility_storage{}.utility_storage_utility_outflow_rate_units xml_buffer, utility_medium_supply{}.utility_solid_medium_supply_utility_type xml_buffer, utility_medium_supply{}.utility_solid_medium_supply_utility_type_codeSpace xml_buffer, utility_role_in_network{}.xlink_href xml_buffer, citygml_appearance{}.xlink_href xml_buffer, utility_function xml_buffer, utility_function_codeSpace xml_buffer, utility_usage{} xml_buffer, utility_usage{}.codeSpace xml_buffer, utility_connected_city_object xml_buffer, utility_year_of_construction xml_date,
      utility_status xml_char(16), utility_location_quality xml_char(12), utility_elevation_quality xml_char(12), utility_consists_of{}.xlink_href xml_buffer, utility_has_material{}.xlink_href xml_buffer, utility_topo_graph_xlink_href xml_buffer, utility_occupied_hollow_space_xlink_href xml_buffer, citygml_level_of_detail{} xml_buffer, utility_class xml_buffer, utility_class_codeSpace xml_buffer, utility_function_of_line xml_buffer, utility_function_of_line_codeSpace xml_buffer, utility_is_gravity xml_boolean, utility_exterior_width xml_real64, utility_exterior_width_units xml_buffer, utility_exterior_height xml_real64, utility_exterior_height_units xml_buffer, utility_exterior_diameter xml_real64, utility_exterior_diameter_units xml_buffer, utility_interior_diameter xml_real64, utility_interior_diameter_units xml_buffer
    -> Counter_12
Note: create id
Counter_12
    SCOPE = Global
    DOMAIN = cityobject_counter
    CNT_ATTR = RoundPipe_id
    START = 1
    -> AttributeKeeper
    -> StringReplacer_4
AttributeKeeper
    KEEP_ATTRS = RoundPipe_id,gml_id,utility_status
    -> AttributeCreator
Note: objectclass_id = 340
AttributeCreator
    ATTR_TABLE = SET_TO objectclass_id = 340
    -> AttributeRenamer
Note: map attributes
AttributeRenamer
    ATTR_TABLE:
      RENAME_SET_DEFAULT RoundPipe_id > id
      RENAME_SET_DEFAULT objectclass_id
      RENAME_SET_DEFAULT utility_status > status
    -> citydb.utn9_network_feature (writer POSTGIS_1) [off]
    -> GeometryRemover
Note: topoGraph xlink: #gmli_id to gml_id
StringReplacer_4
    FIND_TEXT = #
    NO_MATCH = _FME_NO_OP_
    SRC_ATTRS = utility_topo_graph_xlink_href
    CASE = NO
    REGEXP = NO
    -> FeatureMerger [SUPPLIER]

Bookmark: NetworkFeature - OtherShapePipe
OtherShapePipe (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), utility_medium_supply{}.utility_abstract_medium_supply_utility_potential_supply_utility_supply_utility_flow_rate xml_real64, utility_medium_supply{}.utility_abstract_medium_supply_utility_potential_supply_utility_supply_utility_flow_rate_units xml_buffer, utility_medium_supply{}.utility_abstract_medium_supply_utility_potential_supply_utility_supply_utility_status xml_char(16), utility_medium_supply{}.utility_abstract_medium_supply_utility_current_supply_utility_supply_utility_flow_rate xml_real64, utility_medium_supply{}.utility_abstract_medium_supply_utility_current_supply_utility_supply_utility_flow_rate_units xml_buffer, utility_medium_supply{}.utility_abstract_medium_supply_utility_current_supply_utility_supply_utility_status xml_char(16), utility_medium_supply{}.utility_abstract_medium_supply_utility_storage{}.utility_storage_utility_type xml_buffer, utility_medium_supply{}.utility_abstract_medium_supply_utility_storage{}.utility_storage_utility_type_codeSpace xml_buffer, utility_medium_supply{}.utility_abstract_medium_supply_utility_storage{}.utility_storage_utility_max_capacity xml_real64, utility_medium_supply{}.utility_abstract_medium_supply_utility_storage{}.utility_storage_utility_max_capacity_units xml_buffer, utility_medium_supply{}.utility_abstract_medium_supply_utility_storage{}.utility_storage_utility_fill_level xml_real64, utility_medium_supply{}.utility_abstract_medium_supply_utility_storage{}.utility_storage_utility_inflow_rate xml_real64, utility_medium_supply{}.utility_abstract_medium_supply_utility_storage{}.utility_storage_utility_inflow_rate_units xml_buffer, utility_medium_supply{}.utility_abstract_medium_supply_utility_storage{}.utility_storage_utility_outflow_rate xml_real64, utility_medium_supply{}.utility_abstract_medium_supply_utility_storage{}.utility_storage_utility_outflow_rate_units xml_buffer, utility_medium_supply{}.utility_electrical_medium_supply_utility_potential_supply_utility_supply_utility_flow_rate xml_real64,
      utility_medium_supply{}.utility_electrical_medium_supply_utility_potential_supply_utility_supply_utility_flow_rate_units xml_buffer, utility_medium_supply{}.utility_electrical_medium_supply_utility_potential_supply_utility_supply_utility_status xml_char(16), utility_medium_supply{}.utility_electrical_medium_supply_utility_current_supply_utility_supply_utility_flow_rate xml_real64, utility_medium_supply{}.utility_electrical_medium_supply_utility_current_supply_utility_supply_utility_flow_rate_units xml_buffer, utility_medium_supply{}.utility_electrical_medium_supply_utility_current_supply_utility_supply_utility_status xml_char(16), utility_medium_supply{}.utility_electrical_medium_supply_utility_storage{}.utility_storage_utility_type xml_buffer, utility_medium_supply{}.utility_electrical_medium_supply_utility_storage{}.utility_storage_utility_type_codeSpace xml_buffer, utility_medium_supply{}.utility_electrical_medium_supply_utility_storage{}.utility_storage_utility_max_capacity xml_real64, utility_medium_supply{}.utility_electrical_medium_supply_utility_storage{}.utility_storage_utility_max_capacity_units xml_buffer, utility_medium_supply{}.utility_electrical_medium_supply_utility_storage{}.utility_storage_utility_fill_level xml_real64, utility_medium_supply{}.utility_electrical_medium_supply_utility_storage{}.utility_storage_utility_inflow_rate xml_real64, utility_medium_supply{}.utility_electrical_medium_supply_utility_storage{}.utility_storage_utility_inflow_rate_units xml_buffer, utility_medium_supply{}.utility_electrical_medium_supply_utility_storage{}.utility_storage_utility_outflow_rate xml_real64, utility_medium_supply{}.utility_electrical_medium_supply_utility_storage{}.utility_storage_utility_outflow_rate_units xml_buffer, utility_medium_supply{}.utility_electrical_medium_supply_utility_type xml_char(29), utility_medium_supply{}.utility_optical_medium_supply_utility_potential_supply_utility_supply_utility_flow_rate xml_real64, utility_medium_supply{}.utility_optical_medium_supply_utility_potential_supply_utility_supply_utility_flow_rate_units xml_buffer, utility_medium_supply{}.utility_optical_medium_supply_utility_potential_supply_utility_supply_utility_status xml_char(16), utility_medium_supply{}.utility_optical_medium_supply_utility_current_supply_utility_supply_utility_flow_rate xml_real64, utility_medium_supply{}.utility_optical_medium_supply_utility_current_supply_utility_supply_utility_flow_rate_units xml_buffer, utility_medium_supply{}.utility_optical_medium_supply_utility_current_supply_utility_supply_utility_status xml_char(16), utility_medium_supply{}.utility_optical_medium_supply_utility_storage{}.utility_storage_utility_type xml_buffer, utility_medium_supply{}.utility_optical_medium_supply_utility_storage{}.utility_storage_utility_type_codeSpace xml_buffer, utility_medium_supply{}.utility_optical_medium_supply_utility_storage{}.utility_storage_utility_max_capacity xml_real64, utility_medium_supply{}.utility_optical_medium_supply_utility_storage{}.utility_storage_utility_max_capacity_units xml_buffer, utility_medium_supply{}.utility_optical_medium_supply_utility_storage{}.utility_storage_utility_fill_level xml_real64, utility_medium_supply{}.utility_optical_medium_supply_utility_storage{}.utility_storage_utility_inflow_rate xml_real64, utility_medium_supply{}.utility_optical_medium_supply_utility_storage{}.utility_storage_utility_inflow_rate_units xml_buffer, utility_medium_supply{}.utility_optical_medium_supply_utility_storage{}.utility_storage_utility_outflow_rate xml_real64, utility_medium_supply{}.utility_optical_medium_supply_utility_storage{}.utility_storage_utility_outflow_rate_units xml_buffer,
      utility_medium_supply{}.utility_optical_medium_supply_utility_type xml_char(7), utility_medium_supply{}.utility_liquid_medium_supply_utility_potential_supply_utility_supply_utility_flow_rate xml_real64, utility_medium_supply{}.utility_liquid_medium_supply_utility_potential_supply_utility_supply_utility_flow_rate_units xml_buffer, utility_medium_supply{}.utility_liquid_medium_supply_utility_potential_supply_utility_supply_utility_status xml_char(16), utility_medium_supply{}.utility_liquid_medium_supply_utility_current_supply_utility_supply_utility_flow_rate xml_real64, utility_medium_supply{}.utility_liquid_medium_supply_utility_current_supply_utility_supply_utility_flow_rate_units xml_buffer, utility_medium_supply{}.utility_liquid_medium_supply_utility_current_supply_utility_supply_utility_status xml_char(16), utility_medium_supply{}.utility_liquid_medium_supply_utility_storage{}.utility_storage_utility_type xml_buffer, utility_medium_supply{}.utility_liquid_medium_supply_utility_storage{}.utility_storage_utility_type_codeSpace xml_buffer, utility_medium_supply{}.utility_liquid_medium_supply_utility_storage{}.utility_storage_utility_max_capacity xml_real64, utility_medium_supply{}.utility_liquid_medium_supply_utility_storage{}.utility_storage_utility_max_capacity_units xml_buffer, utility_medium_supply{}.utility_liquid_medium_supply_utility_storage{}.utility_storage_utility_fill_level xml_real64, utility_medium_supply{}.utility_liquid_medium_supply_utility_storage{}.utility_storage_utility_inflow_rate xml_real64, utility_medium_supply{}.utility_liquid_medium_supply_utility_storage{}.utility_storage_utility_inflow_rate_units xml_buffer, utility_medium_supply{}.utility_liquid_medium_supply_utility_storage{}.utility_storage_utility_outflow_rate xml_real64, utility_medium_supply{}.utility_liquid_medium_supply_utility_storage{}.utility_storage_utility_outflow_rate_units xml_buffer, utility_medium_supply{}.utility_liquid_medium_supply_utility_type xml_buffer, utility_medium_supply{}.utility_liquid_medium_supply_utility_type_codeSpace xml_buffer, utility_medium_supply{}.utility_gaseous_medium_supply_utility_potential_supply_utility_supply_utility_flow_rate xml_real64, utility_medium_supply{}.utility_gaseous_medium_supply_utility_potential_supply_utility_supply_utility_flow_rate_units xml_buffer, utility_medium_supply{}.utility_gaseous_medium_supply_utility_potential_supply_utility_supply_utility_status xml_char(16), utility_medium_supply{}.utility_gaseous_medium_supply_utility_current_supply_utility_supply_utility_flow_rate xml_real64, utility_medium_supply{}.utility_gaseous_medium_supply_utility_current_supply_utility_supply_utility_flow_rate_units xml_buffer, utility_medium_supply{}.utility_gaseous_medium_supply_utility_current_supply_utility_supply_utility_status xml_char(16), utility_medium_supply{}.utility_gaseous_medium_supply_utility_storage{}.utility_storage_utility_type xml_buffer, utility_medium_supply{}.utility_gaseous_medium_supply_utility_storage{}.utility_storage_utility_type_codeSpace xml_buffer, utility_medium_supply{}.utility_gaseous_medium_supply_utility_storage{}.utility_storage_utility_max_capacity xml_real64, utility_medium_supply{}.utility_gaseous_medium_supply_utility_storage{}.utility_storage_utility_max_capacity_units xml_buffer, utility_medium_supply{}.utility_gaseous_medium_supply_utility_storage{}.utility_storage_utility_fill_level xml_real64, utility_medium_supply{}.utility_gaseous_medium_supply_utility_storage{}.utility_storage_utility_inflow_rate xml_real64,
      utility_medium_supply{}.utility_gaseous_medium_supply_utility_storage{}.utility_storage_utility_inflow_rate_units xml_buffer, utility_medium_supply{}.utility_gaseous_medium_supply_utility_storage{}.utility_storage_utility_outflow_rate xml_real64, utility_medium_supply{}.utility_gaseous_medium_supply_utility_storage{}.utility_storage_utility_outflow_rate_units xml_buffer, utility_medium_supply{}.utility_gaseous_medium_supply_utility_type xml_buffer, utility_medium_supply{}.utility_gaseous_medium_supply_utility_type_codeSpace xml_buffer, utility_medium_supply{}.utility_solid_medium_supply_utility_potential_supply_utility_supply_utility_flow_rate xml_real64, utility_medium_supply{}.utility_solid_medium_supply_utility_potential_supply_utility_supply_utility_flow_rate_units xml_buffer, utility_medium_supply{}.utility_solid_medium_supply_utility_potential_supply_utility_supply_utility_status xml_char(16), utility_medium_supply{}.utility_solid_medium_supply_utility_current_supply_utility_supply_utility_flow_rate xml_real64, utility_medium_supply{}.utility_solid_medium_supply_utility_current_supply_utility_supply_utility_flow_rate_units xml_buffer, utility_medium_supply{}.utility_solid_medium_supply_utility_current_supply_utility_supply_utility_status xml_char(16), utility_medium_supply{}.utility_solid_medium_supply_utility_storage{}.utility_storage_utility_type xml_buffer, utility_medium_supply{}.utility_solid_medium_supply_utility_storage{}.utility_storage_utility_type_codeSpace xml_buffer, utility_medium_supply{}.utility_solid_medium_supply_utility_storage{}.utility_storage_utility_max_capacity xml_real64, utility_medium_supply{}.utility_solid_medium_supply_utility_storage{}.utility_storage_utility_max_capacity_units xml_buffer, utility_medium_supply{}.utility_solid_medium_supply_utility_storage{}.utility_storage_utility_fill_level xml_real64, utility_medium_supply{}.utility_solid_medium_supply_utility_storage{}.utility_storage_utility_inflow_rate xml_real64, utility_medium_supply{}.utility_solid_medium_supply_utility_storage{}.utility_storage_utility_inflow_rate_units xml_buffer, utility_medium_supply{}.utility_solid_medium_supply_utility_storage{}.utility_storage_utility_outflow_rate xml_real64, utility_medium_supply{}.utility_solid_medium_supply_utility_storage{}.utility_storage_utility_outflow_rate_units xml_buffer, utility_medium_supply{}.utility_solid_medium_supply_utility_type xml_buffer, utility_medium_supply{}.utility_solid_medium_supply_utility_type_codeSpace xml_buffer, utility_role_in_network{}.xlink_href xml_buffer, citygml_appearance{}.xlink_href xml_buffer, utility_function xml_buffer, utility_function_codeSpace xml_buffer, utility_usage{} xml_buffer, utility_usage{}.codeSpace xml_buffer, utility_connected_city_object xml_buffer, utility_year_of_construction xml_date,
      utility_status xml_char(16), utility_location_quality xml_char(12), utility_elevation_quality xml_char(12), utility_consists_of{}.xlink_href xml_buffer, utility_has_material{}.xlink_href xml_buffer, utility_topo_graph_xlink_href xml_buffer, utility_occupied_hollow_space_xlink_href xml_buffer, citygml_level_of_detail{} xml_buffer, utility_class xml_buffer, utility_class_codeSpace xml_buffer, utility_function_of_line xml_buffer, utility_function_of_line_codeSpace xml_buffer, utility_is_gravity xml_boolean, utility_exterior_width xml_real64, utility_exterior_width_units xml_buffer, utility_exterior_height xml_real64, utility_exterior_height_units xml_buffer, utility_exterior_diameter xml_real64, utility_exterior_diameter_units xml_buffer
    -> Counter_5
Note: create id
Counter_5
    SCOPE = Global
    DOMAIN = cityobject_counter
    CNT_ATTR = OtherShapePipe_id
    START = 1
    -> StringReplacer_6
    -> AttributeKeeper_8
AttributeKeeper_8
    KEEP_ATTRS = utility_status,OtherShapePipe_id,gml_id
    -> AttributeCreator_10
Note: objectclass_id = 339
AttributeCreator_10
    ATTR_TABLE = SET_TO objectclass_id = 339
    -> AttributeRenamer_12
Note: map attributes
AttributeRenamer_12
    ATTR_TABLE:
      RENAME_SET_DEFAULT OtherShapePipe_id > id
      RENAME_SET_DEFAULT objectclass_id
      RENAME_SET_DEFAULT utility_status > status
    -> GeometryRemover
    -> citydb.utn9_network_feature (writer POSTGIS_1) [off]
Note: topoGraph xlink: #gmli_id to gml_id
StringReplacer_6
    FIND_TEXT = #
    NO_MATCH = _FME_NO_OP_
    SRC_ATTRS = utility_topo_graph_xlink_href
    CASE = NO
    REGEXP = NO
    -> FeatureMerger [SUPPLIER]

Bookmark: FeatureGraph
FeatureGraph (reader CITYGML_1)
    attributes: citygml_target_uri xml_buffer, citygml_feature_role xml_buffer, citygml_feature_role_attr_name xml_buffer, citygml_feature_role_attr_val xml_buffer, gml_description xml_buffer, gml_name xml_buffer, utility_link_member{}.xlink_href xml_buffer, utility_node_member{}.xlink_href xml_buffer
    -> Counter_7
Note: create id
Counter_7
    SCOPE = Local
    DOMAIN = featuregraph_counter
    CNT_ATTR = FeatureGraph_id
    START = 1
    -> FeatureMerger [REQUESTOR]
    -> FeatureMerger_4 [SUPPLIER]
FeatureMerger
    MERGE_TYPE = Attributes Only
    IGNORE_NULLS = No
    REJECT_NULL_MISSING_KEYS = No
    PROCESS_DUPS = No
    JOIN_KEYS = @Value(gml_id) @Value(utility_topo_graph_xlink_href) AUTO
    ATTR_ACCUM_MODE = Merge Supplier
    ATTR_CONFLICT_RES = Use Requestor
    SUPPLIERS_FIRST = No
    MERGED -> FeatureMerger_2 [REQUESTOR]
FeatureMerger_2
    MERGE_TYPE = Attributes Only
    IGNORE_NULLS = No
    REJECT_NULL_MISSING_KEYS = No
    PROCESS_DUPS = No
    JOIN_KEYS = @Value(gml_parent_id) @Value(gml_id) AUTO
    ATTR_ACCUM_MODE = Merge Supplier
    ATTR_CONFLICT_RES = Use Requestor
    SUPPLIERS_FIRST = No
    MERGED -> AttributeKeeper_3
    MERGED -> FeatureMerger_10 [SUPPLIER]
AttributeKeeper_3
    KEEP_ATTRS = SimpleFunctionalElement_id,NetworkGraph_id,RoundPipe_id,OtherShapePipe_id,FeatureGraph_id,gml_id,gml_parent_id
    -> AttributeCreator_3
Note: objectclass_id = 303
AttributeCreator_3
    ATTR_TABLE = SET_TO objectclass_id = 303
    -> AttributeRenamer_3
Note: map attributes
AttributeRenamer_3
    ATTR_TABLE:
      RENAME_SET_DEFAULT NetworkGraph_id > ntw_graph_id
      RENAME_SET_DEFAULT gml_id > gmlid
      RENAME_SET_DEFAULT objectclass_id
      RENAME_SET_DEFAULT RoundPipe_id > ntw_feature_id
      RENAME_SET_DEFAULT SimpleFunctionalElement_id > ntw_feature_id
      RENAME_SET_DEFAULT NetworkGraph_id > ntw_graph_id
      RENAME_SET_DEFAULT FeatureGraph_id > id
      RENAME_SET_DEFAULT OtherShapePipe_id > ntw_feature_id
    -> citydb.utn9_feature_graph (writer POSTGRES_1)

Bookmark: Node
Node (reader CITYGML_1)
    attributes: citygml_target_uri xml_buffer, citygml_feature_role xml_buffer, citygml_feature_role_attr_name xml_buffer, citygml_feature_role_attr_val xml_buffer, gml_description xml_buffer, gml_name xml_buffer, utility_type xml_char(8), utility_connection_signature xml_xml, utility_link_control xml_xml
    -> Counter_6
Note: create id
Counter_6
    SCOPE = Local
    DOMAIN = node_counter
    CNT_ATTR = Node_id
    START = 1
    -> FeatureMerger_4 [REQUESTOR]
    -> FeatureMerger_5 [SUPPLIER]
    -> FeatureMerger_7 [SUPPLIER]
    -> FeatureMerger_6 [SUPPLIER]
    -> FeatureMerger_8 [SUPPLIER]
FeatureMerger_4
    MERGE_TYPE = Attributes Only
    IGNORE_NULLS = No
    REJECT_NULL_MISSING_KEYS = No
    PROCESS_DUPS = No
    JOIN_KEYS = @Value(gml_parent_id) @Value(gml_id) AUTO
    ATTR_ACCUM_MODE = Merge Supplier
    ATTR_CONFLICT_RES = Use Requestor
    SUPPLIERS_FIRST = No
    MERGED -> AttributeKeeper_6
AttributeKeeper_6
    KEEP_ATTRS = utility_type,gml_id,Node_id,FeatureGraph_id
    -> AttributeCreator_6
Note: objectclass_id = 304
AttributeCreator_6
    ATTR_TABLE = SET_TO objectclass_id = 304
    -> AttributeRenamer_6
Note: map attributes
AttributeRenamer_6
    ATTR_TABLE:
      RENAME_SET_DEFAULT Node_id > id
      RENAME_SET_DEFAULT gml_id > gmlid
      RENAME_SET_DEFAULT objectclass_id
      RENAME_SET_DEFAULT utility_type > type
      RENAME_SET_DEFAULT FeatureGraph_id > feat_graph_id
    -> citydb.utn9_node (writer POSTGIS_2) [off]

Bookmark: InterFeatureLink and InteriorFeatureLink
InterFeatureLink (reader CITYGML_1)
    attributes: citygml_target_uri xml_buffer, citygml_feature_role xml_buffer, citygml_feature_role_attr_name xml_buffer, citygml_feature_role_attr_val xml_buffer, gml_description xml_buffer, gml_name xml_buffer, utility_direction xml_char(1), utility_link_control xml_xml, utility_start_xlink_href xml_buffer, utility_end_xlink_href xml_buffer, utility_type xml_char(8)
    -> Counter_3
Note: create id
Counter_3
    SCOPE = Global
    DOMAIN = link_counter
    CNT_ATTR = link_id
    START = 1
    -> StringReplacer_2
Note: remove #
StringReplacer_2
    FIND_TEXT = #
    NO_MATCH = _FME_NO_OP_
    SRC_ATTRS = utility_start_xlink_href,utility_end_xlink_href
    CASE = NO
    REGEXP = NO
    -> FeatureMerger_5 [REQUESTOR]
FeatureMerger_5
    MERGE_TYPE = Attributes Only
    IGNORE_NULLS = No
    REJECT_NULL_MISSING_KEYS = No
    PROCESS_DUPS = No
    JOIN_KEYS = @Value(utility_start_xlink_href) @Value(gml_id) AUTO
    ATTR_ACCUM_MODE = Merge Supplier
    ATTR_CONFLICT_RES = Use Requestor
    SUPPLIERS_FIRST = No
    MERGED -> AttributeRenamer_7
AttributeRenamer_7
    ATTR_TABLE = RENAME_SET_DEFAULT Node_id > start_node_id
    -> FeatureMerger_7 [REQUESTOR]
FeatureMerger_7
    MERGE_TYPE = Attributes Only
    IGNORE_NULLS = No
    REJECT_NULL_MISSING_KEYS = No
    PROCESS_DUPS = No
    JOIN_KEYS = @Value(utility_end_xlink_href) @Value(gml_id) AUTO
    ATTR_ACCUM_MODE = Merge Supplier
    ATTR_CONFLICT_RES = Use Requestor
    SUPPLIERS_FIRST = No
    MERGED -> FeatureMerger_9 [REQUESTOR]
InteriorFeatureLink (reader CITYGML_1)
    attributes: citygml_target_uri xml_buffer, citygml_feature_role xml_buffer, citygml_feature_role_attr_name xml_buffer, citygml_feature_role_attr_val xml_buffer, gml_description xml_buffer, gml_name xml_buffer, utility_direction xml_char(1), utility_link_control xml_xml, utility_start_xlink_href xml_buffer, utility_end_xlink_href xml_buffer
    -> Counter_8
Note: create id
Counter_8
    SCOPE = Global
    DOMAIN = link_counter
    CNT_ATTR = link_id
    START = 1
    -> StringReplacer_5
Note: remove #
StringReplacer_5
    FIND_TEXT = #
    NO_MATCH = _FME_NO_OP_
    SRC_ATTRS = utility_start_xlink_href,utility_end_xlink_href
    CASE = NO
    REGEXP = NO
    -> FeatureMerger_6 [REQUESTOR]
FeatureMerger_6
    MERGE_TYPE = Attributes Only
    IGNORE_NULLS = No
    REJECT_NULL_MISSING_KEYS = No
    PROCESS_DUPS = No
    JOIN_KEYS = @Value(utility_start_xlink_href) @Value(gml_id) AUTO
    ATTR_ACCUM_MODE = Merge Supplier
    ATTR_CONFLICT_RES = Use Requestor
    SUPPLIERS_FIRST = No
    MERGED -> AttributeRenamer_9
AttributeRenamer_9
    ATTR_TABLE = RENAME_SET_DEFAULT Node_id > start_node_id
    -> FeatureMerger_8 [REQUESTOR]
FeatureMerger_8
    MERGE_TYPE = Attributes Only
    IGNORE_NULLS = No
    REJECT_NULL_MISSING_KEYS = No
    PROCESS_DUPS = No
    JOIN_KEYS = @Value(utility_end_xlink_href) @Value(gml_id) AUTO
    ATTR_ACCUM_MODE = Merge Supplier
    ATTR_CONFLICT_RES = Use Requestor
    SUPPLIERS_FIRST = No
    MERGED -> FeatureMerger_10 [REQUESTOR]
FeatureMerger_10
    MERGE_TYPE = Attributes Only
    IGNORE_NULLS = No
    REJECT_NULL_MISSING_KEYS = No
    PROCESS_DUPS = No
    JOIN_KEYS = @Value(gml_parent_id) @Value(gml_id) AUTO
    ATTR_ACCUM_MODE = Merge Supplier
    ATTR_CONFLICT_RES = Use Requestor
    SUPPLIERS_FIRST = No
    MERGED -> AttributeRenamer_10
AttributeRenamer_10
    ATTR_TABLE:
      RENAME_SET_DEFAULT Node_id > end_node_id
      RENAME_SET_DEFAULT link_id > id
      RENAME_SET_DEFAULT gml_id > gmlid
      RENAME_SET_DEFAULT FeatureGraph_id > feat_graph_id
      RENAME_SET_DEFAULT NetworkGraph_id > ntw_graph_id
    -> AttributeCreator_7
Note: objectclass_id = 306
AttributeCreator_7
    ATTR_TABLE = SET_TO objectclass_id = 306
    -> citydb.utn9_link (writer POSTGIS_4) [off]
FeatureMerger_9
    MERGE_TYPE = Attributes Only
    IGNORE_NULLS = No
    REJECT_NULL_MISSING_KEYS = No
    PROCESS_DUPS = No
    JOIN_KEYS = @Value(gml_parent_id) @Value(gml_id) AUTO
    ATTR_ACCUM_MODE = Merge Supplier
    ATTR_CONFLICT_RES = Use Requestor
    SUPPLIERS_FIRST = No
    MERGED -> AttributeRenamer_8
AttributeRenamer_8
    ATTR_TABLE:
      RENAME_SET_DEFAULT Node_id > end_node_id
      RENAME_SET_DEFAULT utility_type > interfeature_link_type
      RENAME_SET_DEFAULT link_id > id
      RENAME_SET_DEFAULT gml_id > gmlid
      RENAME_SET_DEFAULT FeatureGraph_id > feat_graph_id
      RENAME_SET_DEFAULT NetworkGraph_id > ntw_graph_id
    -> AttributeCreator_8
Note: objectclass_id = 307
AttributeCreator_8
    ATTR_TABLE = SET_TO objectclass_id = 307
    -> GeometryRemover_2
GeometryRemover_2
    -> citydb.utn9_link (writer POSTGIS_4) [off]

Bookmark: NetworkGraph
NetworkGraph (reader CITYGML_1)
    attributes: citygml_target_uri xml_buffer, citygml_feature_role xml_buffer, citygml_feature_role_attr_name xml_buffer, citygml_feature_role_attr_val xml_buffer, gml_description xml_buffer, gml_name xml_buffer, utility_feature_graph_member{}.xlink_href xml_buffer, utility_link_member{}.xlink_href xml_buffer, utility_network_link_member{}.xlink_href xml_buffer
    -> Counter_4
Note: create id
Counter_4
    SCOPE = Local
    DOMAIN = networkgraph_counter
    CNT_ATTR = NetworkGraph_id
    START = 1
    -> FeatureMerger_2 [SUPPLIER]
    -> FeatureMerger_3 [REQUESTOR]
    -> FeatureMerger_9 [SUPPLIER]
FeatureMerger_3
    MERGE_TYPE = Attributes Only
    IGNORE_NULLS = No
    REJECT_NULL_MISSING_KEYS = No
    PROCESS_DUPS = No
    JOIN_KEYS = @Value(gml_parent_id) @Value(gml_id) AUTO
    ATTR_ACCUM_MODE = Merge Supplier
    ATTR_CONFLICT_RES = Use Requestor
    SUPPLIERS_FIRST = No
    MERGED -> AttributeKeeper_5
AttributeKeeper_5
    KEEP_ATTRS = gml_id,Network_id,NetworkGraph_id
    -> AttributeCreator_5
Note: objectclass_id = 302
AttributeCreator_5
    ATTR_TABLE = SET_TO objectclass_id = 302
    -> AttributeRenamer_5
Note: map attributes
AttributeRenamer_5
    ATTR_TABLE:
      RENAME_SET_DEFAULT NetworkGraph_id > id
      RENAME_SET_DEFAULT objectclass_id
      RENAME_SET_DEFAULT gml_id > gmlid
      RENAME_SET_DEFAULT Network_id > network_id
    -> citydb.utn9_network_graph (writer POSTGRES_2) [off]

Bookmark: Network
Network (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), utility_medium_supply{}.utility_abstract_medium_supply_utility_potential_supply_utility_supply_utility_flow_rate xml_real64, utility_medium_supply{}.utility_abstract_medium_supply_utility_potential_supply_utility_supply_utility_flow_rate_units xml_buffer, utility_medium_supply{}.utility_abstract_medium_supply_utility_potential_supply_utility_supply_utility_status xml_char(16), utility_medium_supply{}.utility_abstract_medium_supply_utility_current_supply_utility_supply_utility_flow_rate xml_real64, utility_medium_supply{}.utility_abstract_medium_supply_utility_current_supply_utility_supply_utility_flow_rate_units xml_buffer, utility_medium_supply{}.utility_abstract_medium_supply_utility_current_supply_utility_supply_utility_status xml_char(16), utility_medium_supply{}.utility_abstract_medium_supply_utility_storage{}.utility_storage_utility_type xml_buffer, utility_medium_supply{}.utility_abstract_medium_supply_utility_storage{}.utility_storage_utility_type_codeSpace xml_buffer, utility_medium_supply{}.utility_abstract_medium_supply_utility_storage{}.utility_storage_utility_max_capacity xml_real64, utility_medium_supply{}.utility_abstract_medium_supply_utility_storage{}.utility_storage_utility_max_capacity_units xml_buffer, utility_medium_supply{}.utility_abstract_medium_supply_utility_storage{}.utility_storage_utility_fill_level xml_real64, utility_medium_supply{}.utility_abstract_medium_supply_utility_storage{}.utility_storage_utility_inflow_rate xml_real64, utility_medium_supply{}.utility_abstract_medium_supply_utility_storage{}.utility_storage_utility_inflow_rate_units xml_buffer, utility_medium_supply{}.utility_abstract_medium_supply_utility_storage{}.utility_storage_utility_outflow_rate xml_real64, utility_medium_supply{}.utility_abstract_medium_supply_utility_storage{}.utility_storage_utility_outflow_rate_units xml_buffer, utility_medium_supply{}.utility_electrical_medium_supply_utility_potential_supply_utility_supply_utility_flow_rate xml_real64,
      utility_medium_supply{}.utility_electrical_medium_supply_utility_potential_supply_utility_supply_utility_flow_rate_units xml_buffer, utility_medium_supply{}.utility_electrical_medium_supply_utility_potential_supply_utility_supply_utility_status xml_char(16), utility_medium_supply{}.utility_electrical_medium_supply_utility_current_supply_utility_supply_utility_flow_rate xml_real64, utility_medium_supply{}.utility_electrical_medium_supply_utility_current_supply_utility_supply_utility_flow_rate_units xml_buffer, utility_medium_supply{}.utility_electrical_medium_supply_utility_current_supply_utility_supply_utility_status xml_char(16), utility_medium_supply{}.utility_electrical_medium_supply_utility_storage{}.utility_storage_utility_type xml_buffer, utility_medium_supply{}.utility_electrical_medium_supply_utility_storage{}.utility_storage_utility_type_codeSpace xml_buffer, utility_medium_supply{}.utility_electrical_medium_supply_utility_storage{}.utility_storage_utility_max_capacity xml_real64, utility_medium_supply{}.utility_electrical_medium_supply_utility_storage{}.utility_storage_utility_max_capacity_units xml_buffer, utility_medium_supply{}.utility_electrical_medium_supply_utility_storage{}.utility_storage_utility_fill_level xml_real64, utility_medium_supply{}.utility_electrical_medium_supply_utility_storage{}.utility_storage_utility_inflow_rate xml_real64, utility_medium_supply{}.utility_electrical_medium_supply_utility_storage{}.utility_storage_utility_inflow_rate_units xml_buffer, utility_medium_supply{}.utility_electrical_medium_supply_utility_storage{}.utility_storage_utility_outflow_rate xml_real64, utility_medium_supply{}.utility_electrical_medium_supply_utility_storage{}.utility_storage_utility_outflow_rate_units xml_buffer, utility_medium_supply{}.utility_electrical_medium_supply_utility_type xml_char(29), utility_medium_supply{}.utility_optical_medium_supply_utility_potential_supply_utility_supply_utility_flow_rate xml_real64, utility_medium_supply{}.utility_optical_medium_supply_utility_potential_supply_utility_supply_utility_flow_rate_units xml_buffer, utility_medium_supply{}.utility_optical_medium_supply_utility_potential_supply_utility_supply_utility_status xml_char(16), utility_medium_supply{}.utility_optical_medium_supply_utility_current_supply_utility_supply_utility_flow_rate xml_real64, utility_medium_supply{}.utility_optical_medium_supply_utility_current_supply_utility_supply_utility_flow_rate_units xml_buffer, utility_medium_supply{}.utility_optical_medium_supply_utility_current_supply_utility_supply_utility_status xml_char(16), utility_medium_supply{}.utility_optical_medium_supply_utility_storage{}.utility_storage_utility_type xml_buffer, utility_medium_supply{}.utility_optical_medium_supply_utility_storage{}.utility_storage_utility_type_codeSpace xml_buffer, utility_medium_supply{}.utility_optical_medium_supply_utility_storage{}.utility_storage_utility_max_capacity xml_real64, utility_medium_supply{}.utility_optical_medium_supply_utility_storage{}.utility_storage_utility_max_capacity_units xml_buffer, utility_medium_supply{}.utility_optical_medium_supply_utility_storage{}.utility_storage_utility_fill_level xml_real64, utility_medium_supply{}.utility_optical_medium_supply_utility_storage{}.utility_storage_utility_inflow_rate xml_real64, utility_medium_supply{}.utility_optical_medium_supply_utility_storage{}.utility_storage_utility_inflow_rate_units xml_buffer, utility_medium_supply{}.utility_optical_medium_supply_utility_storage{}.utility_storage_utility_outflow_rate xml_real64, utility_medium_supply{}.utility_optical_medium_supply_utility_storage{}.utility_storage_utility_outflow_rate_units xml_buffer,
      utility_medium_supply{}.utility_optical_medium_supply_utility_type xml_char(7), utility_medium_supply{}.utility_liquid_medium_supply_utility_potential_supply_utility_supply_utility_flow_rate xml_real64, utility_medium_supply{}.utility_liquid_medium_supply_utility_potential_supply_utility_supply_utility_flow_rate_units xml_buffer, utility_medium_supply{}.utility_liquid_medium_supply_utility_potential_supply_utility_supply_utility_status xml_char(16), utility_medium_supply{}.utility_liquid_medium_supply_utility_current_supply_utility_supply_utility_flow_rate xml_real64, utility_medium_supply{}.utility_liquid_medium_supply_utility_current_supply_utility_supply_utility_flow_rate_units xml_buffer, utility_medium_supply{}.utility_liquid_medium_supply_utility_current_supply_utility_supply_utility_status xml_char(16), utility_medium_supply{}.utility_liquid_medium_supply_utility_storage{}.utility_storage_utility_type xml_buffer, utility_medium_supply{}.utility_liquid_medium_supply_utility_storage{}.utility_storage_utility_type_codeSpace xml_buffer, utility_medium_supply{}.utility_liquid_medium_supply_utility_storage{}.utility_storage_utility_max_capacity xml_real64, utility_medium_supply{}.utility_liquid_medium_supply_utility_storage{}.utility_storage_utility_max_capacity_units xml_buffer, utility_medium_supply{}.utility_liquid_medium_supply_utility_storage{}.utility_storage_utility_fill_level xml_real64, utility_medium_supply{}.utility_liquid_medium_supply_utility_storage{}.utility_storage_utility_inflow_rate xml_real64, utility_medium_supply{}.utility_liquid_medium_supply_utility_storage{}.utility_storage_utility_inflow_rate_units xml_buffer, utility_medium_supply{}.utility_liquid_medium_supply_utility_storage{}.utility_storage_utility_outflow_rate xml_real64, utility_medium_supply{}.utility_liquid_medium_supply_utility_storage{}.utility_storage_utility_outflow_rate_units xml_buffer, utility_medium_supply{}.utility_liquid_medium_supply_utility_type xml_buffer, utility_medium_supply{}.utility_liquid_medium_supply_utility_type_codeSpace xml_buffer, utility_medium_supply{}.utility_gaseous_medium_supply_utility_potential_supply_utility_supply_utility_flow_rate xml_real64, utility_medium_supply{}.utility_gaseous_medium_supply_utility_potential_supply_utility_supply_utility_flow_rate_units xml_buffer, utility_medium_supply{}.utility_gaseous_medium_supply_utility_potential_supply_utility_supply_utility_status xml_char(16), utility_medium_supply{}.utility_gaseous_medium_supply_utility_current_supply_utility_supply_utility_flow_rate xml_real64, utility_medium_supply{}.utility_gaseous_medium_supply_utility_current_supply_utility_supply_utility_flow_rate_units xml_buffer, utility_medium_supply{}.utility_gaseous_medium_supply_utility_current_supply_utility_supply_utility_status xml_char(16), utility_medium_supply{}.utility_gaseous_medium_supply_utility_storage{}.utility_storage_utility_type xml_buffer, utility_medium_supply{}.utility_gaseous_medium_supply_utility_storage{}.utility_storage_utility_type_codeSpace xml_buffer, utility_medium_supply{}.utility_gaseous_medium_supply_utility_storage{}.utility_storage_utility_max_capacity xml_real64, utility_medium_supply{}.utility_gaseous_medium_supply_utility_storage{}.utility_storage_utility_max_capacity_units xml_buffer, utility_medium_supply{}.utility_gaseous_medium_supply_utility_storage{}.utility_storage_utility_fill_level xml_real64, utility_medium_supply{}.utility_gaseous_medium_supply_utility_storage{}.utility_storage_utility_inflow_rate xml_real64,
      utility_medium_supply{}.utility_gaseous_medium_supply_utility_storage{}.utility_storage_utility_inflow_rate_units xml_buffer, utility_medium_supply{}.utility_gaseous_medium_supply_utility_storage{}.utility_storage_utility_outflow_rate xml_real64, utility_medium_supply{}.utility_gaseous_medium_supply_utility_storage{}.utility_storage_utility_outflow_rate_units xml_buffer, utility_medium_supply{}.utility_gaseous_medium_supply_utility_type xml_buffer, utility_medium_supply{}.utility_gaseous_medium_supply_utility_type_codeSpace xml_buffer, utility_medium_supply{}.utility_solid_medium_supply_utility_potential_supply_utility_supply_utility_flow_rate xml_real64, utility_medium_supply{}.utility_solid_medium_supply_utility_potential_supply_utility_supply_utility_flow_rate_units xml_buffer, utility_medium_supply{}.utility_solid_medium_supply_utility_potential_supply_utility_supply_utility_status xml_char(16), utility_medium_supply{}.utility_solid_medium_supply_utility_current_supply_utility_supply_utility_flow_rate xml_real64, utility_medium_supply{}.utility_solid_medium_supply_utility_current_supply_utility_supply_utility_flow_rate_units xml_buffer, utility_medium_supply{}.utility_solid_medium_supply_utility_current_supply_utility_supply_utility_status xml_char(16), utility_medium_supply{}.utility_solid_medium_supply_utility_storage{}.utility_storage_utility_type xml_buffer, utility_medium_supply{}.utility_solid_medium_supply_utility_storage{}.utility_storage_utility_type_codeSpace xml_buffer, utility_medium_supply{}.utility_solid_medium_supply_utility_storage{}.utility_storage_utility_max_capacity xml_real64, utility_medium_supply{}.utility_solid_medium_supply_utility_storage{}.utility_storage_utility_max_capacity_units xml_buffer, utility_medium_supply{}.utility_solid_medium_supply_utility_storage{}.utility_storage_utility_fill_level xml_real64, utility_medium_supply{}.utility_solid_medium_supply_utility_storage{}.utility_storage_utility_inflow_rate xml_real64, utility_medium_supply{}.utility_solid_medium_supply_utility_storage{}.utility_storage_utility_inflow_rate_units xml_buffer, utility_medium_supply{}.utility_solid_medium_supply_utility_storage{}.utility_storage_utility_outflow_rate xml_real64, utility_medium_supply{}.utility_solid_medium_supply_utility_storage{}.utility_storage_utility_outflow_rate_units xml_buffer, utility_medium_supply{}.utility_solid_medium_supply_utility_type xml_buffer, utility_medium_supply{}.utility_solid_medium_supply_utility_type_codeSpace xml_buffer, utility_role_in_network{}.xlink_href xml_buffer, citygml_appearance{}.xlink_href xml_buffer, utility_class xml_buffer, utility_class_codeSpace xml_buffer, utility_function{} xml_buffer, utility_function{}.codeSpace xml_buffer, utility_usage{} xml_buffer, utility_usage{}.codeSpace xml_buffer,
      utility_transported_medium_xlink_href xml_buffer, utility_sub_network{}.xlink_href xml_buffer, utility_topo_graph_xlink_href xml_buffer, utility_component{}.xlink_href xml_buffer, utility_supplies_xlink_href xml_buffer, utility_sub_ordinate_network{}.xlink_href xml_buffer, utility_super_ordinate_network{}.xlink_href xml_buffer
    -> Counter_9
Note: create CityObject_id
Counter_9
    SCOPE = Global
    DOMAIN = cityobject_counter
    CNT_ATTR = Network_id
    START = 1
    -> FeatureMerger_3 [SUPPLIER]
    -> AttributeKeeper_4
AttributeKeeper_4
    KEEP_ATTRS = gml_id,utility_function{0},Network_id
    -> AttributeCreator_4
Note: objectclass_id = 300
AttributeCreator_4
    ATTR_TABLE = SET_TO objectclass_id = 300
    -> AttributeRenamer_4
Note: map attributes
AttributeRenamer_4
    ATTR_TABLE:
      RENAME_SET_DEFAULT Network_id > id
      RENAME_SET_DEFAULT objectclass_id
      RENAME_SET_DEFAULT utility_function{0} > function
      RENAME_SET_DEFAULT gml_id > gmlid
    -> citydb.utn9_network (writer POSTGRES_3) [off]
    -> citydb.cityobject (writer POSTGRES_4) [off]

Bookmark: CityFurniture
CityFurniture (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), utility_medium_supply{}.utility_abstract_medium_supply_utility_potential_supply_utility_supply_utility_flow_rate xml_real64, utility_medium_supply{}.utility_abstract_medium_supply_utility_potential_supply_utility_supply_utility_flow_rate_units xml_buffer, utility_medium_supply{}.utility_abstract_medium_supply_utility_potential_supply_utility_supply_utility_status xml_char(16), utility_medium_supply{}.utility_abstract_medium_supply_utility_current_supply_utility_supply_utility_flow_rate xml_real64, utility_medium_supply{}.utility_abstract_medium_supply_utility_current_supply_utility_supply_utility_flow_rate_units xml_buffer, utility_medium_supply{}.utility_abstract_medium_supply_utility_current_supply_utility_supply_utility_status xml_char(16), utility_medium_supply{}.utility_abstract_medium_supply_utility_storage{}.utility_storage_utility_type xml_buffer, utility_medium_supply{}.utility_abstract_medium_supply_utility_storage{}.utility_storage_utility_type_codeSpace xml_buffer, utility_medium_supply{}.utility_abstract_medium_supply_utility_storage{}.utility_storage_utility_max_capacity xml_real64, utility_medium_supply{}.utility_abstract_medium_supply_utility_storage{}.utility_storage_utility_max_capacity_units xml_buffer, utility_medium_supply{}.utility_abstract_medium_supply_utility_storage{}.utility_storage_utility_fill_level xml_real64, utility_medium_supply{}.utility_abstract_medium_supply_utility_storage{}.utility_storage_utility_inflow_rate xml_real64, utility_medium_supply{}.utility_abstract_medium_supply_utility_storage{}.utility_storage_utility_inflow_rate_units xml_buffer, utility_medium_supply{}.utility_abstract_medium_supply_utility_storage{}.utility_storage_utility_outflow_rate xml_real64, utility_medium_supply{}.utility_abstract_medium_supply_utility_storage{}.utility_storage_utility_outflow_rate_units xml_buffer, utility_medium_supply{}.utility_electrical_medium_supply_utility_potential_supply_utility_supply_utility_flow_rate xml_real64,
      utility_medium_supply{}.utility_electrical_medium_supply_utility_potential_supply_utility_supply_utility_flow_rate_units xml_buffer, utility_medium_supply{}.utility_electrical_medium_supply_utility_potential_supply_utility_supply_utility_status xml_char(16), utility_medium_supply{}.utility_electrical_medium_supply_utility_current_supply_utility_supply_utility_flow_rate xml_real64, utility_medium_supply{}.utility_electrical_medium_supply_utility_current_supply_utility_supply_utility_flow_rate_units xml_buffer, utility_medium_supply{}.utility_electrical_medium_supply_utility_current_supply_utility_supply_utility_status xml_char(16), utility_medium_supply{}.utility_electrical_medium_supply_utility_storage{}.utility_storage_utility_type xml_buffer, utility_medium_supply{}.utility_electrical_medium_supply_utility_storage{}.utility_storage_utility_type_codeSpace xml_buffer, utility_medium_supply{}.utility_electrical_medium_supply_utility_storage{}.utility_storage_utility_max_capacity xml_real64, utility_medium_supply{}.utility_electrical_medium_supply_utility_storage{}.utility_storage_utility_max_capacity_units xml_buffer, utility_medium_supply{}.utility_electrical_medium_supply_utility_storage{}.utility_storage_utility_fill_level xml_real64, utility_medium_supply{}.utility_electrical_medium_supply_utility_storage{}.utility_storage_utility_inflow_rate xml_real64, utility_medium_supply{}.utility_electrical_medium_supply_utility_storage{}.utility_storage_utility_inflow_rate_units xml_buffer, utility_medium_supply{}.utility_electrical_medium_supply_utility_storage{}.utility_storage_utility_outflow_rate xml_real64, utility_medium_supply{}.utility_electrical_medium_supply_utility_storage{}.utility_storage_utility_outflow_rate_units xml_buffer, utility_medium_supply{}.utility_electrical_medium_supply_utility_type xml_char(29), utility_medium_supply{}.utility_optical_medium_supply_utility_potential_supply_utility_supply_utility_flow_rate xml_real64, utility_medium_supply{}.utility_optical_medium_supply_utility_potential_supply_utility_supply_utility_flow_rate_units xml_buffer, utility_medium_supply{}.utility_optical_medium_supply_utility_potential_supply_utility_supply_utility_status xml_char(16), utility_medium_supply{}.utility_optical_medium_supply_utility_current_supply_utility_supply_utility_flow_rate xml_real64, utility_medium_supply{}.utility_optical_medium_supply_utility_current_supply_utility_supply_utility_flow_rate_units xml_buffer, utility_medium_supply{}.utility_optical_medium_supply_utility_current_supply_utility_supply_utility_status xml_char(16), utility_medium_supply{}.utility_optical_medium_supply_utility_storage{}.utility_storage_utility_type xml_buffer, utility_medium_supply{}.utility_optical_medium_supply_utility_storage{}.utility_storage_utility_type_codeSpace xml_buffer, utility_medium_supply{}.utility_optical_medium_supply_utility_storage{}.utility_storage_utility_max_capacity xml_real64, utility_medium_supply{}.utility_optical_medium_supply_utility_storage{}.utility_storage_utility_max_capacity_units xml_buffer, utility_medium_supply{}.utility_optical_medium_supply_utility_storage{}.utility_storage_utility_fill_level xml_real64, utility_medium_supply{}.utility_optical_medium_supply_utility_storage{}.utility_storage_utility_inflow_rate xml_real64, utility_medium_supply{}.utility_optical_medium_supply_utility_storage{}.utility_storage_utility_inflow_rate_units xml_buffer, utility_medium_supply{}.utility_optical_medium_supply_utility_storage{}.utility_storage_utility_outflow_rate xml_real64, utility_medium_supply{}.utility_optical_medium_supply_utility_storage{}.utility_storage_utility_outflow_rate_units xml_buffer,
      utility_medium_supply{}.utility_optical_medium_supply_utility_type xml_char(7), utility_medium_supply{}.utility_liquid_medium_supply_utility_potential_supply_utility_supply_utility_flow_rate xml_real64, utility_medium_supply{}.utility_liquid_medium_supply_utility_potential_supply_utility_supply_utility_flow_rate_units xml_buffer, utility_medium_supply{}.utility_liquid_medium_supply_utility_potential_supply_utility_supply_utility_status xml_char(16), utility_medium_supply{}.utility_liquid_medium_supply_utility_current_supply_utility_supply_utility_flow_rate xml_real64, utility_medium_supply{}.utility_liquid_medium_supply_utility_current_supply_utility_supply_utility_flow_rate_units xml_buffer, utility_medium_supply{}.utility_liquid_medium_supply_utility_current_supply_utility_supply_utility_status xml_char(16), utility_medium_supply{}.utility_liquid_medium_supply_utility_storage{}.utility_storage_utility_type xml_buffer, utility_medium_supply{}.utility_liquid_medium_supply_utility_storage{}.utility_storage_utility_type_codeSpace xml_buffer, utility_medium_supply{}.utility_liquid_medium_supply_utility_storage{}.utility_storage_utility_max_capacity xml_real64, utility_medium_supply{}.utility_liquid_medium_supply_utility_storage{}.utility_storage_utility_max_capacity_units xml_buffer, utility_medium_supply{}.utility_liquid_medium_supply_utility_storage{}.utility_storage_utility_fill_level xml_real64, utility_medium_supply{}.utility_liquid_medium_supply_utility_storage{}.utility_storage_utility_inflow_rate xml_real64, utility_medium_supply{}.utility_liquid_medium_supply_utility_storage{}.utility_storage_utility_inflow_rate_units xml_buffer, utility_medium_supply{}.utility_liquid_medium_supply_utility_storage{}.utility_storage_utility_outflow_rate xml_real64, utility_medium_supply{}.utility_liquid_medium_supply_utility_storage{}.utility_storage_utility_outflow_rate_units xml_buffer, utility_medium_supply{}.utility_liquid_medium_supply_utility_type xml_buffer, utility_medium_supply{}.utility_liquid_medium_supply_utility_type_codeSpace xml_buffer, utility_medium_supply{}.utility_gaseous_medium_supply_utility_potential_supply_utility_supply_utility_flow_rate xml_real64, utility_medium_supply{}.utility_gaseous_medium_supply_utility_potential_supply_utility_supply_utility_flow_rate_units xml_buffer, utility_medium_supply{}.utility_gaseous_medium_supply_utility_potential_supply_utility_supply_utility_status xml_char(16), utility_medium_supply{}.utility_gaseous_medium_supply_utility_current_supply_utility_supply_utility_flow_rate xml_real64, utility_medium_supply{}.utility_gaseous_medium_supply_utility_current_supply_utility_supply_utility_flow_rate_units xml_buffer, utility_medium_supply{}.utility_gaseous_medium_supply_utility_current_supply_utility_supply_utility_status xml_char(16), utility_medium_supply{}.utility_gaseous_medium_supply_utility_storage{}.utility_storage_utility_type xml_buffer, utility_medium_supply{}.utility_gaseous_medium_supply_utility_storage{}.utility_storage_utility_type_codeSpace xml_buffer, utility_medium_supply{}.utility_gaseous_medium_supply_utility_storage{}.utility_storage_utility_max_capacity xml_real64, utility_medium_supply{}.utility_gaseous_medium_supply_utility_storage{}.utility_storage_utility_max_capacity_units xml_buffer, utility_medium_supply{}.utility_gaseous_medium_supply_utility_storage{}.utility_storage_utility_fill_level xml_real64, utility_medium_supply{}.utility_gaseous_medium_supply_utility_storage{}.utility_storage_utility_inflow_rate xml_real64,
      utility_medium_supply{}.utility_gaseous_medium_supply_utility_storage{}.utility_storage_utility_inflow_rate_units xml_buffer, utility_medium_supply{}.utility_gaseous_medium_supply_utility_storage{}.utility_storage_utility_outflow_rate xml_real64, utility_medium_supply{}.utility_gaseous_medium_supply_utility_storage{}.utility_storage_utility_outflow_rate_units xml_buffer, utility_medium_supply{}.utility_gaseous_medium_supply_utility_type xml_buffer, utility_medium_supply{}.utility_gaseous_medium_supply_utility_type_codeSpace xml_buffer, utility_medium_supply{}.utility_solid_medium_supply_utility_potential_supply_utility_supply_utility_flow_rate xml_real64, utility_medium_supply{}.utility_solid_medium_supply_utility_potential_supply_utility_supply_utility_flow_rate_units xml_buffer, utility_medium_supply{}.utility_solid_medium_supply_utility_potential_supply_utility_supply_utility_status xml_char(16), utility_medium_supply{}.utility_solid_medium_supply_utility_current_supply_utility_supply_utility_flow_rate xml_real64, utility_medium_supply{}.utility_solid_medium_supply_utility_current_supply_utility_supply_utility_flow_rate_units xml_buffer, utility_medium_supply{}.utility_solid_medium_supply_utility_current_supply_utility_supply_utility_status xml_char(16), utility_medium_supply{}.utility_solid_medium_supply_utility_storage{}.utility_storage_utility_type xml_buffer, utility_medium_supply{}.utility_solid_medium_supply_utility_storage{}.utility_storage_utility_type_codeSpace xml_buffer, utility_medium_supply{}.utility_solid_medium_supply_utility_storage{}.utility_storage_utility_max_capacity xml_real64, utility_medium_supply{}.utility_solid_medium_supply_utility_storage{}.utility_storage_utility_max_capacity_units xml_buffer, utility_medium_supply{}.utility_solid_medium_supply_utility_storage{}.utility_storage_utility_fill_level xml_real64, utility_medium_supply{}.utility_solid_medium_supply_utility_storage{}.utility_storage_utility_inflow_rate xml_real64, utility_medium_supply{}.utility_solid_medium_supply_utility_storage{}.utility_storage_utility_inflow_rate_units xml_buffer, utility_medium_supply{}.utility_solid_medium_supply_utility_storage{}.utility_storage_utility_outflow_rate xml_real64, utility_medium_supply{}.utility_solid_medium_supply_utility_storage{}.utility_storage_utility_outflow_rate_units xml_buffer, utility_medium_supply{}.utility_solid_medium_supply_utility_type xml_buffer, utility_medium_supply{}.utility_solid_medium_supply_utility_type_codeSpace xml_buffer, utility_role_in_network{}.xlink_href xml_buffer, citygml_appearance{}.xlink_href xml_buffer, citygml_class xml_buffer, citygml_class_codeSpace xml_buffer, citygml_function{} xml_buffer, citygml_function{}.codeSpace xml_buffer, citygml_usage{} xml_buffer, citygml_usage{}.codeSpace xml_buffer,
      citygml_level_of_detail{} xml_buffer
    -> Counter_10
Note: create CityObject_id
Counter_10
    SCOPE = Global
    DOMAIN = cityobject_counter
    CNT_ATTR = CityFurniture_id
    START = 1
    -> FeatureMerger_12 [SUPPLIER]
    -> AttributeKeeper_7
AttributeKeeper_7
    KEEP_ATTRS = CityFurniture_id,gml_id,citygml_class
    -> AttributeCreator_9
Note: objectclass_id = 21
AttributeCreator_9
    ATTR_TABLE = SET_TO objectclass_id = 21
    -> AttributeRenamer_11
Note: map attributes
AttributeRenamer_11
    ATTR_TABLE:
      RENAME_SET_DEFAULT CityFurniture_id > id
      RENAME_SET_DEFAULT citygml_class > class
      RENAME_SET_DEFAULT objectclass_id
      RENAME_SET_DEFAULT gml_id > gmlid
    -> citydb.city_furniture (writer POSTGIS_3) [off]
    -> citydb.cityobject (writer POSTGRES_4) [off]
